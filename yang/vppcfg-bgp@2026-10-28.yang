module vppcfg-bgp {
    yang-version 1.1;
    namespace "urn:clixon-vppcfg:params:xml:ns:yang:vppcfg-bgp";
    prefix bgp;

    organization "clixon-vppcfg";
    contact "https://github.com/najiebhaswell/clixon-vppcfg";
    description
        "BGP configuration for BIRD 3. Every Clixon commit renders this model to
         /etc/bird/bird-clixon.conf (included from the hand-written bird.conf),
         validates it with 'bird -p' and applies it with 'birdc configure'.

         Peers without a policy accept and announce nothing (RFC 8212).
         Hand-written BIRD filters can be referenced by name with
         import-filter/export-filter.

         Copyright 2026 Najieb Haswell. Licensed under the Apache License, Version 2.0.";

    revision 2026-10-28 {
        description "Phase 2: router-id, BGP peers and peer-groups, networks, prefix-lists,
                     community-lists, route-policies.";
    }

    typedef asn {
        type uint32 {
            range "1..4294967295";
        }
    }
    typedef ip-address {
        type string {
            pattern '[0-9.]+|[0-9a-fA-F:.]+';
        }
        description "IPv4 or IPv6 address (checked in full by the helper).";
    }
    typedef ip-prefix {
        type string {
            pattern '[0-9.]+/[0-9]{1,2}|[0-9a-fA-F:.]+/[0-9]{1,3}';
        }
    }
    typedef object-name {
        type string {
            length "1..48";
            pattern '[A-Za-z][A-Za-z0-9_-]*';
        }
    }
    typedef community {
        type string {
            pattern '[0-9]{1,5}:[0-9]{1,5}';
        }
        description "Standard community ASN:value.";
    }
    typedef large-community {
        type string {
            pattern '[0-9]{1,10}:[0-9]{1,10}:[0-9]{1,10}';
        }
        description "Large community (RFC 8092) ASN:data1:data2, each part 0..4294967295.";
    }
    typedef action {
        type enumeration {
            enum permit;
            enum deny;
        }
    }

    grouping af-settings {
        leaf activate {
            type boolean;
            description "Exchange routes of this family. Default: true for the family of the
                         neighbor address, false otherwise.";
        }
        leaf import-policy { type object-name; description "route-policy for received routes."; }
        leaf export-policy { type object-name; description "route-policy for announced routes."; }
        leaf import-filter { type object-name; description "Hand-written BIRD filter; overrides import-policy."; }
        leaf export-filter { type object-name; description "Hand-written BIRD filter; overrides export-policy."; }
        leaf max-prefix {
            type uint32 {
                range "1..4294967295";
            }
            description "Restart the session when more routes are received.";
        }
        leaf next-hop-self { type boolean; }
    }

    grouping peer-settings {
        leaf remote-as { type asn; }
        leaf description {
            type string {
                length "1..80";
                pattern '[^"]*';
            }
        }
        leaf source-address { type ip-address; }
        leaf password {
            type string {
                length "1..80";
                pattern '[^"]*';
            }
            description "TCP MD5 password.";
        }
        leaf multihop {
            type uint8 {
                range "1..255";
            }
        }
        leaf bfd { type boolean; }
        leaf hold-time {
            type uint16 {
                range "3..65535";
            }
        }
        leaf keepalive {
            type uint16 {
                range "1..65535";
            }
        }
        leaf shutdown { type boolean; }
        leaf reflect-client {
            type boolean;
            description "This router is a route reflector and the IBGP peer its client.
                         Set for the session in BIRD, in all address families.";
        }
        leaf allow-local-as {
            type uint8 { range "1..10"; }
            description "Accept received routes with up to this many local AS numbers in the AS path.
                         Set for the session in BIRD, in all address families.";
        }
        container ipv4 { uses af-settings; }
        container ipv6 { uses af-settings; }
    }

    container routing {
        leaf router-id {
            type string {
                pattern '[0-9]+[.][0-9]+[.][0-9]+[.][0-9]+';
            }
        }
        container bgp {
            leaf local-as { type asn; }
            list network {
                key prefix;
                leaf prefix { type ip-prefix; }
                description "Own prefixes, originated as static blackhole routes.";
            }
            list peer-group {
                key name;
                leaf name { type object-name; }
                uses peer-settings;
            }
            list neighbor {
                key address;
                leaf address { type ip-address; }
                leaf peer-group { type object-name; }
                leaf name {
                    type string {
                        length "1..32";
                        pattern '[A-Za-z][A-Za-z0-9_]*';
                    }
                    description "Name of the session in BIRD (birdc show protocols).
                                 Default: cx_ followed by the address. Renaming restarts the session.";
                }
                uses peer-settings;
            }
        }
        list static-route {
            key "prefix destination";
            description "Static routes, in BIRD protocols cx_static4 and cx_static6. A prefix can have one
                         destination: the key allows a commit to refuse a second one instead of replacing it.";
            leaf prefix { type ip-prefix; }
            leaf destination {
                type union {
                    type ip-address;
                    type enumeration { enum blackhole; }
                }
                description "Next hop, or blackhole to discard the traffic.";
            }
            leaf prepend {
                type string {
                    pattern '[0-9]{1,10}( [0-9]{1,10}){0,9}';
                }
                description "AS numbers put in the AS path of the route, leftmost first.";
            }
        }
        container rpki {
            description "RPKI origin validation: cache servers reached with the RPKI-to-Router
                         protocol. All servers feed the same ROA tables.";
            list session {
                key address;
                leaf address { type ip-address; }
                leaf port {
                    type uint16 { range "1..65535"; }
                    description "TCP port of the cache server. Default: 323.";
                }
                leaf source-address { type ip-address; description "Source address of the session."; }
                leaf refresh {
                    type uint32 { range "1..86399"; }
                    units seconds;
                    description "Polling interval. Default: 3600, or the value sent by the server.";
                }
                leaf retry {
                    type uint32 { range "1..7200"; }
                    units seconds;
                    description "Wait after a failed poll. Default: 600, or the value sent by the server.";
                }
                leaf aging {
                    type uint32 { range "600..172800"; }
                    units seconds;
                    description "ROAs are deleted when they could not be refreshed for this time.
                                 Default: 7200, or the value sent by the server.";
                }
            }
        }
        list prefix-list {
            key name;
            leaf name { type object-name; }
            list entry {
                key seq;
                leaf seq {
                    type uint32 {
                        range "1..4294967295";
                    }
                }
                leaf action { type action; }
                leaf prefix { type ip-prefix; }
                leaf ge {
                    type uint8 {
                        range "1..128";
                    }
                }
                leaf le {
                    type uint8 {
                        range "1..128";
                    }
                }
            }
        }
        list community-list {
            key name;
            leaf name { type object-name; }
            leaf-list community {
                type community;
            }
        }
        list as-path-list {
            key name;
            leaf name { type object-name; }
            description "AS-path list: entries are tried in seq order, the first match decides
                         (permit or deny); no match is deny.";
            list entry {
                key seq;
                leaf seq {
                    type uint32 {
                        range "1..4294967295";
                    }
                }
                leaf action { type action; }
                choice pattern {
                    leaf regex {
                        type string {
                            length "1..200";
                            pattern '[^" ;]+';
                        }
                        description "Cisco/Huawei AS-path regular expression, translated to a BIRD path
                                     mask (checked by the helper). Supported: ^ $ _ .* [0-9]+ AS numbers
                                     and (A|B|C).";
                    }
                    leaf bird-mask {
                        type string {
                            length "5..200";
                            pattern '[^";]+';
                        }
                        description "BIRD path mask used as is, e.g. [= * 64512..65534 * =].";
                    }
                }
            }
        }
        list large-community-list {
            key name;
            leaf name { type object-name; }
            leaf-list large-community {
                type large-community;
            }
        }
        list route-policy {
            key name;
            leaf name { type object-name; }
            list node {
                key seq;
                leaf seq {
                    type uint32 {
                        range "1..4294967295";
                    }
                }
                leaf action { type action; }
                container match {
                    leaf prefix-list { type object-name; }
                    leaf community-list { type object-name; }
                    leaf large-community-list { type object-name; }
                    leaf as-path-list { type object-name; }
                    leaf as-path-contains { type asn; }
                    leaf origin-as { type asn; }
                    leaf rpki {
                        type enumeration {
                            enum valid;
                            enum invalid;
                            enum not-found;
                        }
                        description "Origin validation result of the route. Routes without an origin AS
                                     (own networks, an empty AS path) are not-found.";
                    }
                }
                container set {
                    leaf local-preference { type uint32; }
                    leaf preference {
                        type uint16 { range "1..65535"; }
                        description "Route preference in BIRD: selects between protocols, before any BGP
                                     attribute. Higher is preferred, unlike VRP and IOS. Defaults: BGP 100,
                                     static 200, direct 240.";
                    }
                    leaf med { type uint32; }
                    leaf-list community { type community; }
                    leaf-list large-community { type large-community; }
                    leaf prepend {
                        type string {
                            pattern '[0-9]{1,10}( [0-9]{1,10}){0,9}';
                        }
                        description "AS numbers put in front of the AS path, leftmost first (Cisco
                                     'set as-path prepend 65000 65000', Huawei 'apply as-path 65000 65000
                                     additive'). On EBGP sessions BIRD adds the local AS in front of these.";
                    }
                }
            }
        }
    }
}
